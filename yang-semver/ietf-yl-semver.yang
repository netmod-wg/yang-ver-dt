module ietf-yl-semver {
  yang-version 1.1;
  namespace "urn:ietf:params:xml:ns:yang:ietf-yl-semver";
  prefix yl-semver;

  import ietf-semver {
    prefix semver;
  }
  
  import ietf-yang-library {
    prefix yanglib;
  }

  organization
    "IETF NETMOD (Network Modeling) Working Group";
  contact
    "WG Web:   <https://datatracker.ietf.org/wg/netmod/>
     WG List:  <mailto:netmod@ietf.org>

     Author:   Benoit Claise
               <mailto:bclaise@cisco.com>

     Author:   Joe Clarke
               <mailto:jclarke@cisco.com>

     Author:   Reshad Rahman
               <mailto:rrahman@cisco.com>

     Author:   Robert Wilton
               <mailto:rwilton@cisco.com>

     Author:   Kevin D'Souza
               <mailto:kd6913@att.com>

     Author:   Balazs Lengyel
               <mailto:balazs.lengyel@ericsson.com>

     Author:   Jason Sterne
               <mailto:jason.sterne@nokia.com>";
  description
    "This module contains augmentations to YANG Library to add module
     level semantic version numbers and to provide an indication of
     how deprecated and obsolete nodes are handled by the server.";

    semver:module-version "0.1.0";

  revision 2019-02-27 {
    description
      "Moved YANG library augmentations into a separate module.";
    reference
      "draft-verdt-netmod-yang-semver: 
       YANG Semantic Versioning for Modules";
    semver:module-version "0.1.0";
  }

  augment "/yanglib:yang-library/yanglib:module-set/yanglib:module" {
    description
      "Augmentation modules with a semantic version.";
    leaf version {
      type semver:version;
      description
        "The semantic version for this module.  The version MUST
         match the semver:version value in specific revision of the
         module loaded in this module-set.";
      reference
        "draft-verdt-netmod-yang-semver: YANG Semantic Versioning";
    }
  }

  augment "/yanglib:yang-library/yanglib:schema" {
    description
      "Augmentations to the ietf-yang-library module to indicate how
       deprecated and obsoleted nodes are handled for each datastore
       schema supported by the server.";

    leaf deprecated-nodes-implemented {
      type empty;
      description
        "If present, this leaf indicates that all schema nodes with a
         status 'deprecated' child statement are implemented
         equivalently as if they had status 'current', or otherwise
         deviations MUST be used to explicitly remove 'deprecated'
         nodes from the schema.  If this leaf is absent then the
         behavior is unspecified.";
      reference
        "draft-verdt-netmod-yang-semver: Reporting how deprecated and
         obsolete nodes are handled";
    }
    leaf obsolete-nodes-absent {
      type empty;
      description
        "If present, this leaf indicates that the server does not
         implement any status 'obsolete' nodes.  If this leaf is
         absent then the behaviour is unspecified.";
      reference
        "draft-verdt-netmod-yang-semver: Reporting how deprecated and
         obsolete nodes are handled";
    }
  }
}
