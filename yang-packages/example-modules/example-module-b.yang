module example-module-b {
  yang-version 1.1;
  namespace "https://example.org/yang/example-module-b";
  prefix b;

  import ietf-yang-semver {
    prefix ys;
  }
  import example-module-b-types {
    prefix bt;
  }

  description
    "Illustrative module for the YANG Packages resolution examples.";

  revision 2026-01-01 {
    ys:version 1.1.0;
    description "Initial illustrative revision.";
  }

  feature bar {
    description "Enable the illustrative value leaf.";
  }

  grouping b-data {
    description "Reusable illustrative data.";
    leaf value {
      if-feature bar;
      type bt:example-string;
      description "An illustrative value.";
    }
  }

  container b {
    description "Illustrative B data.";
    uses b-data;
  }
}
