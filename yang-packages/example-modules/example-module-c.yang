module example-module-c {
  yang-version 1.1;
  namespace "https://example.org/yang/example-module-c";
  prefix c;

  import ietf-yang-semver {
    prefix ys;
  }
  import example-module-a {
    prefix a;
  }

  description
    "Illustrative module C reusing module A for the YANG Packages
     resolution examples.";

  revision 2026-02-01 {
    ys:version 2.0.0;
    description "Initial illustrative revision.";
  }

  container c {
    description "Illustrative C data using module A.";
    uses a:a-data;
  }
}
