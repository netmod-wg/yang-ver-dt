module example-module-b-types {
  yang-version 1.1;
  namespace "https://example.org/yang/example-module-b-types";
  prefix bt;

  import ietf-yang-semver {
    prefix ys;
  }

  description
    "Illustrative types for the YANG Packages resolution examples.";

  revision 2026-01-01 {
    ys:version 1.1.0;
    description "Initial illustrative revision.";
  }

  typedef example-string {
    type string;
    description "An illustrative string type.";
  }
}
