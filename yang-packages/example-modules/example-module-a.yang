module example-module-a {
  yang-version 1.1;
  namespace "https://example.org/yang/example-module-a";
  prefix a;

  import ietf-yang-semver {
    prefix ys;
  }
  import example-module-a-types {
    prefix at;
  }

  description
    "Illustrative module for the YANG Packages resolution examples.";

  revision 2026-01-01 {
    ys:version 1.0.0;
    description "Initial illustrative revision.";
  }

  feature foo {
    description "Enable the illustrative value leaf.";
  }

  grouping a-data {
    description "Reusable illustrative data.";
    leaf value {
      if-feature foo;
      type at:example-string;
      description "An illustrative value.";
    }
  }

  container a {
    description "Illustrative A data.";
    uses a-data;
  }
}
