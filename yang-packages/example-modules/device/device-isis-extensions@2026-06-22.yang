module device-isis-extensions {
  yang-version 1.1;
  namespace "urn:example:yang:device-isis-extensions";
  prefix disis;

  import ietf-yang-semver {
    prefix ys;
  }

  description
    "Module identity fixture for the hypothetical device examples.
     Device-specific extension data is outside the scope of this fixture.";

  revision 2026-06-22 {
    ys:version 1.2.4_compatible;
    description "Illustrative revision for the package examples.";
  }
}
