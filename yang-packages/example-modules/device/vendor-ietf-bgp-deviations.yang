module vendor-ietf-bgp-deviations {
  yang-version 1.1;
  namespace "urn:example:yang:vendor-ietf-bgp-deviations";
  prefix vbgp;

  description
    "Module identity fixture for the hypothetical vendor deviation
     module.  Device-specific deviations are outside this fixture's scope.";

  revision 2026-06-22 {
    description "Illustrative revision for the package examples.";
  }
}
