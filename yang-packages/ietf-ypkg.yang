module ietf-ypkg {
  yang-version 1.1;
  namespace "urn:ietf:params:xml:ns:yang:ietf-ypkg";
  prefix ypkg;

  import ietf-yang-semver  {
    prefix ys;
    reference "RFC XXXX: YANG Semantic Versioning";
  }

  import ietf-yang-package-types {
    prefix pkg-types;
    ys:recommended-min-version 0.10.0;
    reference "RFC XXXX: YANG Packages";
  }

  import ietf-yang-structure-ext {
    prefix sx;
    reference "RFC 8791: YANG Data Structure Extensions.";
  }

  import ietf-inet-types {
    prefix inet;
    reference "RFC 9911: Common YANG Data Types";
  }

  organization
    "IETF NETMOD (Network Modeling) Working Group";

  contact
    "WG Web:   <https://datatracker.ietf.org/wg/netmod/>
     WG List:  <mailto:netmod@ietf.org>

     Editor:   Robert Wilton
               <mailto:rwilton@cisco.com>";

  description
    "This module defines the structure of a YANG package file
     encoded using the JSON encoding specified in RFC 7951.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,

     they appear in all capitals, as shown here.";

  revision 2026-07-06 {
    ys:version 0.10.0;
    description
      "Initial revision";
    reference
      "RFC XXXX: YANG Packages";
  }


  /*
   * Package file grouping and structure
   */

  grouping yang-package-file {
    description
      "Defines a schema reference and a complete
       package definition.";

    leaf schema {
      type pkg-types:pkg-reference;
      description
        "Identifies the package defining the schema for the entire
         package file as '<package-name>@<version>', including the
         envelope and any extensions. The referenced schema MUST be
         referentially complete. If absent, the reference schema
         defined in RFC XXXX applies. The schema package version
         identifies the file format; no separate format version
         is required.";
    }

    leaf-list schema-location {
      type inet:uri;
      ordered-by user;
      description
        "URLs from which the schema package identified by 'schema',
         or the default reference schema when 'schema' is absent,
         can be retrieved. A retrieved package's name and version
         MUST match the schema package reference. If a canonical
         location is provided, it MUST be the first entry.

         If no location is specified, the schema package MUST be
         available to download at the URL formed by appending
         '<pkg-name>@<pkg-version>.ypkg' to
         'https://www.iana.org/assignments/yang-parameters/', using
         the name and version of the explicitly identified or
         default schema package. Otherwise, at least one download
         URL MUST be provided in this leaf-list.";
    }

    leaf-list schema-location-sha-256 {
      type pkg-types:sha-256-hash;
      must "count(../schema-location-sha-256) = "
         + "count(../schema-location)" {
        error-message
          "Each schema location must have a checksum entry.";
      }
      ordered-by user;
      description
        "Optional file checksums corresponding to 'schema-location'.
         If present, this leaf-list MUST have the same number of
         entries, in the same order. Identical files at different
         locations have repeated checksum values.";
    }

    container pkg-defn {
      description
        "The complete package definition carried by this file.";

      uses pkg-types:yang-pkg-instance;
    }
  }

  sx:structure yang-package {
    must "pkg-defn" {
      error-message
        "A package file must contain a package definition.";
    }
    description
      "Defines a YANG package file. All applicable YANG constraints
       and package definition rules MUST be satisfied.
       Values equal to their applicable YANG defaults MAY be
       explicitly encoded, but SHOULD be omitted.";

    uses yang-package-file;
  }
}
