module ietf-semver {
  yang-version 1.1;
  namespace "urn:ietf:params:xml:ns:yang:ietf-semver";
  prefix semver;

  import ietf-yang-library {
    prefix yanglib;
  }

  organization
    "IETF NETMOD (Network Modeling) Working Group";
  contact
    "WG Web:   <https://datatracker.ietf.org/wg/netmod/>
     WG List:  <mailto:netmod@ietf.org>

     Author:   Benoit Claise
               <mailto:bclaise@cisco.com>

     Author:   Joe Clarke
               <mailto:jclarke@cisco.com>

     Author:   Kevin D'Souza
               <mailto:kd6913@att.com>

     Author:   Balazs Lengyel
               <mailto:balazs.lengyel@ericsson.com>";
  description
    "This module contains a definition for a YANG 1.1 extension to
     express the semantic version of YANG modules.";

  revision 2018-04-05 {
    description
      "* Properly import ietf-yang-library.
       * Fix the name of module-semver => module-version.
       * Fix regular expression syntax.
       * Augment yang-library with booleans as to whether or not
         deprecated and obsolete nodes are present.
       * Add an extension to enable import by semantic version.
       * Add an extension status-description to track deprecated
         and obsolete reasons.
       * Fix yang-library augments to use 7895bis.";
    reference
      "draft-clacla-netmod-yang-model-update:
       New YANG Module Update Procedure";
    semver:module-version "0.2.1";
  }
  revision 2017-12-15 {
    description
      "Initial revision.";
    reference
      "draft-clacla-netmod-yang-model-update:
       New YANG Module Update Procedure";
    semver:module-version "0.1.1";
  }

  extension module-version {
    argument semver;
    description
      "The version number for the module revision it is used in.
       This is expressed as a semantic version string in the form:
        x.y.z
       where:
        * x corresponds to the major version,
        * y corresponds to a minor version,
        * z corresponds to a patch version.

       A major version number of 0 indicates that this model is still
       in development, and is potentially subject to change.

       Following a release of major version 1, all modules will
       increment major revision number where backwards incompatible
       changes to the model are made.

       The minor version is changed when features are added to the
       model that do not impact current clients use of the model.
       When major version is stepped, the minor version is reset to 0.

       The patch-level version is incremented when non-feature changes
       (such as bugfixes or clarifications to human-readable
       descriptions that do not impact model functionality) are made
       that maintain backwards compatibility.
       When major or minor version is stepped, the patch-level is
       reset to 0.

       By comparing the module-version between two revisions of a
       given module, one can know if different revisions are backwards
       compatible or not, as well as
       whether or not new features have been added to a newer revision.

       If a module contains this extension it indicates that for this
       module the updated status and update rules as this described in
       RFC XXXX are used.

       The statement MUST only be a substatement of the revision statement.
       Zero or one module-version statement is allowed per parent
       statement. NO substatements are allowed.
      ";
    reference "http://semver.org/ : Semantic Versioning 2.0.0";
  }

  extension import-versions {
    argument version-clause;
    description
      "This extension specifies an acceptable set of semantic versions of a given module
       that may be imported.  The version-clause argument is specified in the following
       format

       [\\[(]X[.Y[.Z]][-[X[.Y[.X]]][\\])]][,...]

       Where the first character MAY be a '[' or '(' to indicate at least inclusive and at least
        exclusive (respectively).  If this is omitted, a full semantic version must be specified
        and the import will only support this one version.

       The following version, if specified with a '[' or '(' indicates the lower bound.  This can
        be a full semantic version or a MAJOR only or MAJOR.MINOR only.

       The '-', if specified, is a literal hyphen indicating a range will be specified.  If the second portion
        of the import-versions clause is omitted, then there is no upper bound on what will be considered
        an acceptable imported version.

       After the '-' the upper bound semantic version (or part thereof) follows.
       After the upper bound version, one of ']' or ')' MUST follow to indicate whether this limit is inclusive
        or exclusive of the upper bound respectively.

       Finally, a literal comma (',') MAY be specified with additional ranges.  Each range is taken as a logical
        OR.

       The statement MUST only be a substatement of the import statement.  Zero or one
       import-versions statement is allowed per import statement.  NO substatements are allowed.";
    reference "I-D.clacla-netmod-yang-model-update : Import By Semantic Version";
  }

  extension status-description {
    argument description;
    description
      "Freeform text that describes why a given node has been deprecated or made obsolete.
       This may point to other schema elements that can be used in lieu of the given node.

       This statement MUST only be used as a substatement of the status statement, and MUST
       only be used when the status is deprecated or obsolete.  Zero or more status-description
       statements are allowed per parent statement.  NO substatements are allowed.";
    reference "I-D.clacla-netmod-yang-model-update : Deprecated and Obsolete Reasons";
  }

  augment "/yanglib:yang-library/yanglib:module-set/yanglib:module" {
    description
      "Augmentations for the ietf-yang-library module to support semantic versioning.";
    leaf module-version {
      type string {
        pattern '[0-9]+\.[0-9]+\.[0-9]+';
      }
      description
        "The semantic version for this module in MAJOR.MINOR.PATCH format.  This version
         must match the semver:module-version value in specific revision of the module
         loaded in this module-set.";
    }
    leaf deprecated-nodes-present {
      type boolean;
      default "true";
      description
        "A boolean that indicates whether or not this server implements deprecated nodes.
         The value of this leaf SHOULD be true; and if so, the server MUST implement nodes
         within this module as they are documented.  If specific deprecated nodes are not
         implemented as document, then they MUST be listed as deviations.";
    }
    leaf obsolete-nodes-present {
      type boolean;
      default "false";
      description
        "A boolean that indicates whether or not this server implements obsolete nodes.
         The value of this leaf SHOULD be false; and if so, the server MUST NOT implement
         nodes within this module. If this leaf is true, then all nodes in this module MUST
         be implemented as documented in the module.  Any variation of this MUST be listed as
         deviations.";
    }
  }
  augment "/yanglib:yang-library/yanglib:module-set/yanglib:module/yanglib:submodule" {
    description
      "Augmentations for the ietf-yang-library module/submodule to support semantic versioning.";
    leaf submodule-version {
      type string {
        pattern '[0-9]+\.[0-9]+\.[0-9]+';
      }
      description
        "The semantic version for this submodule in MAJOR.MINOR.PATCH format.  This version
         must match the semver:module-version value in specific revision of the submodule
         loaded in this module-set.";
    }
  }
}
