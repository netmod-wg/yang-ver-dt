module ietf-schema-selection {
  yang-version 1.1;
  namespace
    "urn:ietf:params:xml:ns:yang:ietf-schema-selection";
  prefix "ver-sel";

  import ietf-datastores {
    prefix ds;
    reference
      "RFC 8342: Network Management Datastore Architecture (NMDA)";
  }

  import ietf-yang-library {
    prefix yanglib;
    reference "RFC 8525: YANG Library";
  }

  import ietf-yl-packages {
    prefix yl-pkg;
    reference "RFC XXXX: YANG Packages";
  }

  organization
    "IETF NETMOD (Network Modeling) Working Group";

  contact
    "WG Web:   <http://tools.ietf.org/wg/netmod/>
     WG List:  <mailto:netmod@ietf.org>

     Author:   Reshad Rahman
               <mailto:rrahman@cisco.com>

     Author:   Rob Wilton
               <mailto:rwilton@cisco.com>";

  description
    "This module provide a data model to advertise and allow the
     selection of schema versions by clients.

     Copyright (c) 2019 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  // RFC Ed.: update the date below with the date of RFC publication
  // and remove this note.
  // RFC Ed.: replace XXXX with actual RFC number and remove this
  // note.
  revision 2019-11-29 {
    description
      "Initial revision";
    reference
      "RFC XXXX: YANG Schema Version Selection";
  }

  /*
   * Features
   */
  feature "default-schema" {
    description
      "Feature that allows clients to choose the default schema set
       to be used for clients.

       Implementations may choose to only support this feature in
       <operational> to report the default-schema-set without
       allowing it to be configured.";
  }

  feature "secondary-schema" {
    description
      "Feature to choose if secondary schema may be configured by
       clients.

       Implementations may choose to only support this feature in
       <operational> to report secondary schema sets without
       allowing them to be configured.";
  }

  feature "custom-schema" {
    if-feature "default-schema or secondary-schema";
    description
      "Feature to choose whether clients may configurable custom
       schema definitions.";
  }

  container schema-selection {
    description
      "YANG schema selection.

       Contains configuration and state related to client selectable
       YANG schema versions.";
        
    leaf default-schema {
      if-feature "default-schema";
      type leafref {
        path "/schema-selection/schema/name";
        require-instance false;
      }
      description
        "Specifies the default schema used by this device.

         This is the schema that is chosen if a NETCONF client doesn't
         select a schema during capability negotiation, or if the
         standard RESTCONF (or NMDA datastore URLs) are used.

         This schema also represents the datastore schema that is used
         to persist configuration for all conventional configuration
         datastores.

         If not configured, the operational state indicates the
         default schema used by this device.";
    }

    leaf-list secondary-schema {
      if-feature "secondary-schema";
      type leafref {
        path "/schema-selection/schema/name";
        require-instance false;
      }
      description
        "Specifies the secondary schema used by this device, that can
         be selected by clients (either through NETCONF capability
         negotiation or RESTCONF schema specific path).";
    }

    list custom-schema {
      if-feature "custom-schema";
      key "name";

      description
        "Defines a custom selectable schema constructed from
         compatible schema";
      
      leaf name {
        type "string";
        description
          "Name of custom schema.

           Format can either be the form of a YANG identifer, or
           '<name>@<rev-label>'.

           The selectable-schema name is used in NETCONF capabilties
           negotiation and also the RESTCONF path (XXX, is encoding
           required, e.g. for '@'?)";
      }

      leaf description {
        type string;
        description
          "The description associated with this custom package.";
      }

      leaf-list included-schema {
        type leafref {
          path "/schema-selection/schema/name";
          require-instance false;
        }
        description
          "Lists the schema that are combined together into a single
           selectable schema (i.e. via a union operation on each
           datastore schema package).";
      }
    }
    
    list schema {
      key "name";
      config false;

      description
        "All available pan-datastore schema that can be used in schema
         version selection.";
      
      leaf name {
        type string;

        description
          "Name of the schema.

           Do we restrict what is allowed, specifically, do we allow
           '@'";
      }
      
      list datastores {
        key "datastore";

        description
          "The list of datastores supported for this pan-datastore
           selectable-package, along with the package schema
           associated with that datastore.";

        leaf datastore {
          type ds:datastore-ref;
          description
            "The datastore that this datastore schema is associated
             with";
          reference
            "RFC 8342: Network Management Datastore Architecture
             (NMDA)";
        }

        container package {
          description
            "YANG package associated with this datastore schema";
          
          leaf name {
            type leafref {
              path "/yanglib:yang-library/yl-pkg:package/yl-pkg:name";
            }
            description
              "The name of the YANG package this schema relates to";
          }
          
          leaf version {
            type leafref {
              path '/yanglib:yang-library/'
                + 'yl-pkg:package[yl-pkg:name = current()/../name]/'
                + 'yl-pkg:version';
            }
            
            description
              "The version of the YANG package this schema relates
               to";
          }

          leaf checksum {
            type leafref {
              path '/yanglib:yang-library/'
                + 'yl-pkg:package[yl-pkg:name = current()/../name]'
                + '[yl-pkg:version = current()/../version] '
                + '/yl-pkg:checksum';
            }

            description
              "The checksum of the references package.";
          }
        }
      }

      container default-schema-selectable {
        if-feature "default-schema";
        presence
          "This schema MAY be selected as the device default
           schema.";
        description
          "Defines compatibility if this schema can be selected as a
           primary schema.";
        
        leaf-list compatible-secondary-schema {
          type leafref {
            path "/schema-selection/schema/name";
          }
          description
            "Lists other schema that MAY be selected as secondary
             schema is this schema is selected as a default-schema.";
        }
      }

      container secondary-schema-selectable {
        if-feature "secondary-schema";
        presence
            "This schema MAY be selected as a secondary schema,
             selected for a particular session.";
        description
          "Defines compatibility if this schema can be selected as a
           secondary schema.";

        leaf-list compatible-default-schema {
          type leafref {
            path "/schema-selection/schema/name";
          }
          description
            "Lists other schema that MAY be selected as the default
             schema at ths same time as this schema is selected as a
             secondary-schema.";
        }

        leaf-list compatible-secondary-schema {
          type leafref {
            path "/schema-selection/schema/name";
          }
          description
            "Lists other schema that MAY be selected as other secondary
             schema is this schema is selected as a secondary-schema.";
        }
      }

      container custom-schema-selectable {
        if-feature "custom-schema";
        presence
          "This schema MAY be selected as part of a custom schema.";
        description
          "Defines compatibility if this schema can be combined as
           part of a custom schema.";

        leaf-list combinable-schema {
          type leafref {
            path "/schema-selection/schema/name";
          }
          description
            "Lists the schema that MAY be combined with this
             schema into a single custom schema'.";
        }
      }
    }
  }
}
